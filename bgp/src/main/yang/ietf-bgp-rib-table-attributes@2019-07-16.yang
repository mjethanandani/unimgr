submodule ietf-bgp-rib-table-attributes {
  yang-version "1.1";
  belongs-to ietf-bgp {
    prefix "br";
  }

  // import some basic types
  import ietf-yang-types {
    prefix types;
    reference
      "RFC 6991, Common YANG Data Types.";
  }

  include ietf-bgp-rib-types;
  
  organization
    "IETF IDR Working Group";

  contact
    "WG Web:   <http://tools.ietf.org/wg/idr>
     WG List:  <idr@ietf.org>

     Authors: Mahesh Jethanandani (mjethanandani at gmail.com),
              Keyur Patel (keyur at arrcus.com),
              Susan Hares (shares at ndzh.com";

  description
    "This submodule contains common data definitions for data
     related to a RIB entry, or RIB table.";


  revision "2019-07-16" {
    description
      "Initial version.";
    reference
      "RFC XXXX: BGP YANG Model for Service Provider Network.";
  }

  grouping bgp-common-route-annotations-state {
    description
      "Data definitions for flags and other information attached
       to routes in both LOC-RIB and Adj-RIB";

    leaf last-modified {
      type types:timeticks;
      description
        "Timestamp when this path was last modified.

         The value is the timestamp in seconds relative to
         the Unix Epoch (Jan 1, 1970 00:00:00 UTC).";
    }

    leaf valid-route {
      type boolean;
      description
        "Indicates that the route is considered valid by the
         local router";
    }

    leaf invalid-reason {
      type identityref {
        base invalid-route-reason;
      }
      description
        "If the route is rejected as invalid, this indicates the
         reason.";
    }
  }

  grouping bgp-loc-rib-route-annotations-state {
    description
      "Data definitions for information attached to routes in the
       LOC-RIB";

       // placeholder for route metadata specific to the LOC-RIB
  }

  grouping bgp-adj-rib-in-post-route-annotations-state {
    description
      "Data definitions for information attached to routes in the
       Adj-RIB-in post-policy table";

    leaf best-path {
      type boolean;
      description
        "Current path was selected as the best path.";
    }
  }

  grouping bgp-common-table-attrs-state {
    description
      "Common attributes attached to all routing tables";

      // placeholder for metadata associated with all tables
  }

  grouping bgp-common-table-attrs-top {
    // no enclosing container as this data will fit under an
    // existing LOC-RIB container

    uses bgp-common-table-attrs-state;
    description
      "Operational state data for data related to the entire
       LOC-RIB";
  }
}
